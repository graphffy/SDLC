// SysML v2 Model: RepetitioUseCases
// Generated by SysML Web IDE

package RepetitioUseCases {
  part def RepetitioSystem;

  part def User {
    flow from User to Login;
    flow from User to ViewStatistics;
    flow from User to CompleteRevision;
    flow from User to ViewReadiness;
    flow from User to EditResult;
    flow from User to ViewWeakTopics;
  }

  use case def Register {
    flow from Register to User;
  }

  use case def Login;

  use case def ManageExams {
    flow from ManageExams to User;
  }

  use case def ManageTopics {
    flow from ManageTopics to User;
  }

  use case def ViewSchedule {
    flow from ViewSchedule to User;
  }

  use case def CompleteRevision;

  use case def EnterResult {
    flow from EnterResult to User;
  }

  use case def EditResult;

  use case def ViewWeakTopics;

  use case def ViewReadiness;

  use case def ViewStatistics;
}

// Element overrides
// @pos "RepetitioUseCases::RepetitioSystem" 370,140
// @pos "RepetitioUseCases::User" 400,360
// @pos "RepetitioUseCases::Register" 390,230
// @pos "RepetitioUseCases::Login" 680,230
// @pos "RepetitioUseCases::ManageTopics" 110,420
// @pos "RepetitioUseCases::ViewSchedule" 100,230
// @pos "RepetitioUseCases::CompleteRevision" 690,420
// @pos "RepetitioUseCases::EnterResult" 110,510
// @pos "RepetitioUseCases::EditResult" 310,510
// @pos "RepetitioUseCases::ViewWeakTopics" 500,510
// @pos "RepetitioUseCases::ViewReadiness" 690,510
// @pos "RepetitioUseCases::ViewStatistics" 690,320
// @size "RepetitioUseCases" 782,596
